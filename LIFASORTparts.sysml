package lifasort {
    package parts {

        /* Composants du système LIFASORT */
        part def CapteurPresence;
        part def ControleurCentral;
        part def CapteurOptique;
        part def MecanismeTri;
        part def Compacteur;
        part def CapteurRemplissage;
        part def Supervision;

        /* Données échangées */
        part def CategorieDechet;
        part def NiveauRemplissage;
        part def Alerte;
    }
}
